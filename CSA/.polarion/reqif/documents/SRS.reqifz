# SRS

# Specification: System Requirements Specification (SRS)

## CSA-2818: INTRODUCTION (Heading)

## CSA-2819: SCOPE (Heading)

### CSA-2820: Main Functions and Interfaces (Heading)

### CSA-2821: Applicable GxP Requirements (Heading)

### CSA-2822: Other Applicable Regulations, Policies, and Procedures (Heading)

## CSA-2823: User Requirements (Heading)

### CSA-2824: General Requirements (Heading)

#### CSA-2825: Product Requirement and Planning (Heading)

##### CSA-2826 (User Requirement)
User shall be able to define the product design and development process required deliverables for a specific product

#### CSA-3070: User Needs, Intended Use, Marketing Claims and Regulatory Management (Heading)

##### CSA-2827 (User Requirement)
The system shall provide user the ability to reuse the contents or a subset thereof of a User Needs document classified by Product Family to create a product specific Design Inputs Summary (DIS) document.

##### CSA-2828 (User Requirement)
The system shall provide the users ability to review a document and move it through its workflow before manually exporting the document for official release and archiving to Master Control

##### CSA-2829 (User Requirement)
The system shall provide users ability to modify content shared across multiple Polarion projects

##### CSA-2830 (User Requirement)
The system shall provide users ability to add a new item to a document shared across multiple projects

##### CSA-2831 (User Requirement)
The system shall provide users ability to define, identify, track (linkage of work items) and report on User Needs, Intended Use, Marketing Claims and Instructions for Use work items (incorporated in DIR document).

##### CSA-2832 (User Requirement)
The system shall provide users ability to report on or query where Work Items are in use, and their document state where they appear.

##### CSA-2833 (User Requirement)
The system shall provide users ability to tag specific revisions of a document leveraging the “Document Baselines” function to those two revisions of the document may be compared.

##### CSA-2834 (User Requirement)
The system shall provide users ability to output a project or document state driven report:
1. Trace Work Items shared across multiple projects;
2. Perform Gap Analysis – based on System tracking of work items that are not completed in the linked configuration.
3. Perform Impact Analysis – based on System providing the links associated with a particular work item eg linked work items impacted by a change to a specific work item

#### CSA-2835: Design Requirements Management (Heading)

##### CSA-2836 (User Requirement)
The system shall provide user the ability to reuse the contents or a subset thereof of another Design Inputs Requirements (DIR) document either from the current project or another project

##### CSA-2837 (User Requirement)
The system shall provide user the ability to review a document and move it through its workflow before export to external system (e.g., Master Control) and approval in said system (Master Control)

##### CSA-2839 (User Requirement)
The system shall provide users with ability to identify, define, trace (linkage of work items to each other), and reporting Design Requirements as they address User Needs, Intended Use, Marketing Claims and Regulatory requirements.

##### CSA-2840 (User Requirement)
The system shall provide users with ability to link defects and associated Annex A/Annex G code with the appropriate image or graphic.

##### CSA-2841 (User Requirement)
The system shall provide users ability to report on or query where Work Items are in use, and their document state as related to the document workflows.

##### CSA-2842 (User Requirement)
The system shall provide users ability to manage the change of existing and addition of new requirements in documents shared across multiple Polarion projects.

##### CSA-2843 (User Requirement)
The system shall provide users ability to output a project or document state driven report:
Trace Work Items shared across multiple projects;
Perform Gap Analysis – based on System tracking of work items that are not completed in the linked configuration;
Perform Impact Analysis – based on System providing the links associated with a particular work item eg linked work items impacted by a change to a specific work item
The system may provide excel type reports showing work items and their linked work items

##### CSA-2844 (User Requirement)
The system shall allow users to manually over-write automated or calculated entries for roles with appropriate access and authorization.

#### CSA-2845: Design Outputs Index (Heading)

##### CSA-2846 (User Requirement)
The system shall provide User to assign Design Output objects from the Master Product Library as they satisfy Design Requirements called out in the project Design Input Requirements document (DIR)

##### CSA-2847 (User Requirement)
The system shall provide users with ability to reuse product Design Output reference records within and across projects.

##### CSA-2848: The system shall allow reporting or querying of where items are in use. (User Requirement)

##### CSA-2849 (User Requirement)
The system shall provide users ability to output a project or document state driven report:
Trace Work Items shared across multiple projects;
Perform Gap Analysis – based on System tracking of work items that are not completed in the linked configuration;
Perform Impact Analysis – based on System providing the links associated with a particular work item eg linked work items impacted by a change to a specific work item

#### CSA-2850: Design Validation and Verification (Heading)

##### CSA-2851 (User Requirement)
The system shall provide ability to the User to perform preliminary DV&V testing on a requirement prior to formal verification activities

##### CSA-2852 (User Requirement)
The system shall provide ability to the User to add, edit and / or view the coverage of requirements down to execution results of test cases

##### CSA-2853 (User Requirement)
The system shall provide user the ability to author Design Validation and Verification Test Plans, Protocols, and Reports.

##### CSA-2854 (User Requirement)
The system shall provide users the ability to identify, define and select Test Methods as they correspond to Risk Levels (Acceptance criteria e.g. Conf/Rel) and Design Requirements which they validate or verify.

#### CSA-2856: Test Method Management (Heading)

##### CSA-2857 (User Requirement)
The system allows user to reuse the contents or a subset thereof of a Test Method document either from the Test Method Library, the current project, or another project.

##### CSA-2858 (User Requirement)
The system shall provide user the ability to execute test methods and record results directly in Polarion.

#### CSA-2859: Risk Management (Heading)

##### CSA-2860 (User Requirement)
The system shall allow user to build Use FMEA based on Instructions for Use (IFU) and User Needs and provide report and selected calculated fields

##### CSA-2861 (User Requirement)
User shall be able to Build Design FMEA based on Use FMEA and provide report
Refer to dFMEA test cases for additional details

##### CSA-2862 (User Requirement)
User shall be able to build Process FMEA based on Design FMEA and Process Flow Diagram report

##### CSA-2863 (User Requirement)
The system shall provide users ability to connect/link potential causes, hazards, hazardous situations and harms to corresponding risk estimates.

##### CSA-2864 (User Requirement)
The system shall allow the ability to define, track and report Harms, Benefits and Risks (Benefit to Risk Analysis output).
Note: The Benefits and Risk Analysis may be authored in Polarion. It links to the harms associated with highest Severity (Severity 4, 5) and Risk Levels (3, 4) in all FMEAs. Report or query necessary in Polarion FMEAs to sort Severity and Risk Level in descending order for linkage.

##### CSA-2865 (User Requirement)
The system shall provide users ability to manually update new content in FMEA based on PPA.
The system shall provide users ability to compare two versions of FMEA – existing version versus new version with updated probability estimates, for example, based on output from PPA.

#### CSA-2867: Manufacturing Process Control Plan (Heading)

##### CSA-2868 (User Requirement)
The system shall provide user the ability to author a Process Control Plan based on process flow diagram and process(p)FMEA that includes following information:
Part Number List
Requirements (EIS / Product) (Standard)
CQ (Material)
IQ (Conditions - Equipment, fixtures, etc.)
OQ & PQ (Process Steps)
Test Method
Frequency
Reaction (Work Instruction)
Control Plan connects the process FMEA risk information, ie [Product/Process Step/Failure Mode/ Effect/ Severity/Causes/Probability (P)/Risk Level] to the Control related information as referenced in the pFMEA ie [Controls/Control Document #’s [SOPs, Test Methods, TMV, Qualification documents] with linkage to the Work Items incorporated.

#### CSA-2869: Test Method Validation Management (Heading)

##### CSA-2870 (User Requirement)
The system shall provide users the ability to show the Test Method Validation acceptance criteria and associated results for a particular Test Method

##### CSA-2871: The system shall provide users ability to identify and define TMV protocols (User Requirement)

#### CSA-2872: Shared Libraries Management (Heading)

##### CSA-2873 (User Requirement)
The system shall allow user to modify content in a shared library (to add/ create new items and remove items)

##### CSA-2874 (User Requirement)
The system shall define and provide user ability to reuse of a Master User Needs Library
i.e., a Table across the entire server displaying User Needs and their associated product
User input narrowing down scope to a product family or product

##### CSA-2875 (User Requirement)
The system shall provide definition and reuse of a Validation Master Plan Library/report.
User input select site across server. Display Table list of IQ, OQ, PQ, CQ, TMV and other defined qualification types

#### CSA-2876: Reports (Heading)

##### CSA-2877 (User Requirement)
The system shall provide the ability to user to generate Risk report. (e.g., xFMEA or Hazard Analysis)

##### CSA-2878 (User Requirement)
The system shall provide the ability to generate a report showing test case coverage for requirements in Polarion

##### CSA-2879: The system shall provide the ability to generate a Multi-level Trace table. (User Requirement)

##### CSA-2880: The system shall allow users to generate reports associated with Library content (User Requirement)

### CSA-2881: Security Requirements (Heading)

#### CSA-2882: User Roles (Heading)

##### CSA-2883: Administrator - <<Description>> (User Requirement)

##### CSA-2884: Coordinator- <<Description>> (User Requirement)

##### CSA-2885: Peer Reviewer- <<Description>> (User Requirement)

##### CSA-2886: Quality- <<Description>> (User Requirement)

#### CSA-2887: Application Security (Heading)

##### CSA-2888 (User Requirement)
The system shall meet Application Security requirements as defined per the Application’s Security Requirements.

### CSA-2889: 21 CFR PART 11 (Heading)

#### CSA-2890: Electronic Records and Electronic Signature (Heading)

##### CSA-2891: The system shall provide ability to restrict access based on user roles (User Requirement)

##### CSA-2892 (User Requirement)
The system shall protect records and preserve their content and enable accurate retrieval

##### CSA-2893 (User Requirement)
The system shall prompt approvers to provide electronic signatures at specified points in the process

##### CSA-2894 (User Requirement)
The system shall make all signatures available for viewing in the audit trail of the record

##### CSA-2895 (User Requirement)
The system shall ensure that signed electronic records clearly indicate the printed name of the signer, date and time when the signature was executed and the associated meaning.

##### CSA-2896 (User Requirement)
The system shall ensure that electronic signatures are unique to each individual.

##### CSA-2897 (User Requirement)
The system’s electronic signature shall be made up of displayed and unmasked USER ID and a Non displayed or masked password.

#### CSA-2898: Audit Trail (Heading)

##### CSA-2899 (User Requirement)
The system shall provide a secure computer generated, time stamped audit trail to record the date and time of the operator entries and actions that create or modify electronic records

##### CSA-2900 (User Requirement)
The system shall ensure the audit trail includes the original electronic record along with the date and time stamp is not lost and the new audit record with date and time stamp modification is recorded, the old and new values or with a reason of change.

### CSA-3071: Interfaces (Heading)

## CSA-2902: GLOSSARY (Heading)

## CSA-2903: Functional Requirements (Heading)

### CSA-2904: General Functions (Heading)

#### CSA-2905: Product Requirement and Planning (Heading)

##### CSA-2906 (Functional Requirement)
The user shall be able to view the activities and deliverables of the following phases of the Design and Development process in the Polarion per definition and lifecycle maintenance of the Design and Development Plan (DDP).
1. Approval
2. Project details
3. Project Team Members
4. Design Reviews
5. Planning
6. Development
7. Pre-submission
8. Qualification
9. Personnel Training and Competencies* - this is optional for Phase 1, retained herein for Phase 2+ consideration.
Document: Refer to Design Development Plan (DDP) Form

##### CSA-2907 (Functional Requirement)
User shall be able to Track and identify the required deliverables through all phases of the product's development.

#### CSA-3072: User Needs, Intended Use, Marketing Claims and Regulatory Management (Heading)

##### CSA-2908: The system shall provide user the ability to BRANCH or REUSE document * If branc... (Functional Requirement)
The system shall provide user the ability to BRANCH or REUSE document
- If branched, the user identifies whether they wish to specify a certain revision to freeze at, or to float with the Head of the original
- If reused, user chooses either clone/copy or derived options depending on the degree of design ownership the user is endowed with for this product.

##### CSA-2909 (Functional Requirement)
The system shall provide user the ability to branch or reuse document to the appropriate project and space

##### CSA-2910: The system shall provide user the ability to remove items that are not needed (Functional Requirement)

##### CSA-2911 (Functional Requirement)
The system shall provide the ability to utilize a document with appropriate lifecycle and restrictions

##### CSA-2912 (Functional Requirement)
The system shall provide user, if branched the ability to overwrite specific to the new device or product and subsequently these changes in master or branch could be MERGED to the other.

##### CSA-2913 (Functional Requirement)
The system shall provide document owner ability to request one or more users to Review

##### CSA-2914 (Functional Requirement)
The system shall provide Document Owner(s) (as defined by the business or business process) ensures document is in appropriate STATUS to allow changes only as desired and to lock other users or items from edit.
Typical status states are “draft”, “review”, “approved” and “release” but these states are fully configurable per Polarion functionality.
Ref 2.2.1 (9) SD-462 Guidance to BD-PI Functional Specification

##### CSA-2915: The system shall provide Reviewers to use document comment feature to Comment (Functional Requirement)

##### CSA-2916 (Functional Requirement)
The system shall provide ability to Mark a Comment as Resolved once the comment change is implemented or denied.

##### CSA-2917 (Functional Requirement)
The system shall provide document owner ability to identify document as ready for export to the external system (e.g., Master Control) once peer review is completed.

##### CSA-2918 (Functional Requirement)
The system shall provide document owner ability to perform updates in Polarion and re-export to external system (e.g., Master Control) until approval is reached in the external system (e.g., Master Control)

##### CSA-2919 (Functional Requirement)
The system shall provide Document owner ability to mark the Polarion document as approved and ensures all document level fields are correct.

##### CSA-2920 (Functional Requirement)
The system shall provide approved version of the document to be available as an historic revision to compare and report against

##### CSA-2921 (Functional Requirement)
The system shall provide Document owner ability to move the document status back to create a new pending revision to approve when internal process dictates.

##### CSA-2922 (Functional Requirement)
The system provides user the ability to identify content that needs to be changed

##### CSA-2923 (Functional Requirement)
The system provides ability to the document owner of the master document, to make the changes after determining the impact of items below

##### CSA-2924 (Functional Requirement)
The system provides ability to the document owner of the branched document, to check the current state of the master and update the item

##### CSA-2925 (Functional Requirement)
The system provides ability to the document owner of the branched document to overwrites and changes the item themselves

##### CSA-2926 (Functional Requirement)
The system provides ability to the document owner of the master document to merge changes back to their document

##### CSA-2927 (Functional Requirement)
The system shall “auto-suspect” flagging to flag child work items when their related parent has changed.
Note: The “suspect” flag appears as a red triangle with a question mark in the middle and is a filterable characteristic

##### CSA-2928 (Functional Requirement)
The system shall provide users ability to identify missing items in their document.

##### CSA-2929 (Functional Requirement)
The system shall provide users ability to add new items to their document be it a Master or Branch

##### CSA-2930 (Functional Requirement)
The system shall provide owner of the other document to make the decision to add the new item to their document.

##### CSA-2931 (Functional Requirement)
The system shall provide owner of the other document to make the decision to prevent the addition of the new item to their document.

##### CSA-2932: The system shall provide user the ability to select the following: * Identificat... (Functional Requirement)
The system shall provide user the ability to select the following:
1. Identification and selection of patient and health care provider User Needs.
2. Identification and selection of medical device Marketing Claims.
3. Identification and selection of product Intended Use Requirements.
4. Defining, tracking, and reporting User Needs, Intended Use, and Marketing Claims
5. Documenting Instructions for Use (IFU) for the product.
6. Reuse of User Needs, Intended Use, and Product Development Requirements and their associated items within and across projects
7. Provide origination and authoring in addition to lifecycle management (collaboration and status within Polarion) for Documents containing User Needs, Intended User, Product Development Requirements (Design Input Summary – DIS).
Note: Typical document states are “draft”, “review”, and “release” but Polarion is not limited in defined states in the lifecycle.

##### CSA-2933: The system shall provide user the ability to select the following: * Facilitate... (Functional Requirement)
The system shall provide user the ability to select the following:
1. Facilitate peer reviews and release of Documents into external document systems, e.g. Master Control
2. Allow reporting or querying of where Work Items are in use, and their state as related to the Document workflow states of the Document where they appear

##### CSA-2934: The system shall provide user the ability to select the following: * Leverage “D... (Functional Requirement)
The system shall provide user the ability to select the following:
1. Leverage “Document Baselines” to tag specific revisions of a particular document.

##### CSA-2935: The system shall provide user the ability to select the following: * Manage the... (Functional Requirement)
The system shall provide user the ability to select the following:
1. Manage the change of existing and addition of new requirements in documents shared across multiple Polarion projects
2. Show traceability, gap analysis, and impact analysis of user needs and requirements shared across multiple projects in both project and state driven manners
Note: The system shall provide excel type reports showing work items and their linked work items

#### CSA-2936: Design Requirements Management (Heading)

##### CSA-2937: The system shall provide the user the ability to BRANCH or REUSE document * If b... (Functional Requirement)
The system shall provide the user the ability to BRANCH or REUSE document
- If branched, the user identifies whether they wish to specify a certain revision to freeze at, or to float with the Head (latest) of the original. At any time, the user can unfreeze/freeze to a different revision.
- If reused, user chooses either clone/copy or derived options depending on the degree of design ownership the user is endowed with for this product.

##### CSA-2938 (Functional Requirement)
The system shall provide the ability to branch or reuse the document to the appropriate project as specified by the user.

##### CSA-2939 (Functional Requirement)
The system shall provide the ability to remove items if a subset is desired by the user

##### CSA-2940 (Functional Requirement)
The system shall provide user the ability for content to be overwritten specific to the new device or product and subsequently these changes in master or branch could be MERGED to the other, if branched.

##### CSA-2941 (Functional Requirement)
The system shall provide ability for a Document utilized with appropriate lifecycle and restrictions.

##### CSA-2942 (Functional Requirement)
The system shall allow the Document owner to request one or more users to REVIEW the document

##### CSA-2943 (Functional Requirement)
The system shall provide Document Owner(s) (as defined by the business or business process) ensures document is in appropriate STATUS to allow changes only as desired and to lock other users or items from edit.
Note: Typical status states are "draft", "review", and "release" but these states are fully configurable per Polarion functionality.
Ref 2.2.1 (9) SD-462 Guidance to BD-PI Functional Specification

##### CSA-2944: The system shall provide Reviewers to use document comment feature to Comment (Functional Requirement)

##### CSA-2945 (Functional Requirement)
The system shall provide ability to Mark a Comment as Resolved once the comment change is implemented or denied.

##### CSA-2946 (Functional Requirement)
The system shall provide document owner ability to identify document as ready for export to the external system (e.g., Master Control) once peer review is completed.

##### CSA-2947 (Functional Requirement)
The system shall provide document owner ability to perform updates in Polarion and re-export to external system (e.g., Master Control) until approval is reached in the external system (e.g., Master Control)

##### CSA-2948 (Functional Requirement)
The system shall provide Document owner ability to mark the Polarion document as approved and ensures all document level fields are correct.

##### CSA-2949 (Functional Requirement)
The system shall provide approved version of the document to be available as an historic revision to compare and report against. The system will provide document baseline function as mechanism to tag a document version for comparison with the released version.

##### CSA-2950 (Functional Requirement)
The system shall provide Document owner ability to move the document status back to create a new pending revision to approve when internal process dictates.

##### CSA-2955: The system shall provide user the ability to select the following: * Identificat... (Functional Requirement)
The system shall provide user the ability to select the following:
1. Identification and definition of product Design Requirements.
2. Defining, tracing (linkage of work items to each other), and reporting Design Requirements as they address User Needs, Intended Use, and Marketing Claims
3. Reuse of product Design Requirements and their associated items within and across projects
4. Provide lifecycle management (collaboration and status within Polarion) for Documents containing Design Requirements (Design Input Requirements- DIR)

##### CSA-2956: The system shall provide user the ability to select the following: * Developing... (Functional Requirement)
The system shall provide user the ability to select the following:
1. Developing Defect Diagrams based on Design and Field inputs (data).

##### CSA-2957: The system shall provide user the ability to select the following: * Provide doc... (Functional Requirement)
The system shall provide user the ability to select the following:
1. Provide documents to facilitate peer reviews and release into external document systems, e.g. Master Control
2. Allow reporting or querying of where items are in use, and their state as related to the Document Workflows

##### CSA-2958: The system shall provide user the ability to select the following: * Show tracea... (Functional Requirement)
The system shall provide user the ability to select the following:
1. Show traceability, gap analysis, and impact analysis of requirements shared across multiple projects in both project and state driven manners.
Typically, these are excel type reports showing work items and their linked work items.

#### CSA-2959: Design Outputs Index (Heading)

##### CSA-2960 (Functional Requirement)
The system shall allow users to open DIR document and navigate to Design Requirements Work items.

##### CSA-2961 (Functional Requirement)
The system shall allow users to use sidebar control "Edit Links" to link associated Design Output work item(s).

##### CSA-2962 (Functional Requirement)
The system shall allow users to save document and audits linkages via a Design Requirement coverage report.

##### CSA-2963: The system shall provide user the ability to select the following: * Allow repor... (Functional Requirement)
The system shall provide user the ability to select the following:
1. Allow reporting or querying of where items are in use.
2. Show traceability, gap analysis, and impact analysis of requirements shared across multiple projects in both project and state driven manners
Note: The system may provide excel type reports showing work items and their linked work items

#### CSA-2964: Design Validation and Verification (Heading)

##### CSA-2965 (Functional Requirement)
The system shall allow user to create a new suite (or test script i.e., "Test Run") of Test Methods (template) reflecting that this is for preliminary test method evaluation and not Formal Verification or Validation testing

##### CSA-2966 (Functional Requirement)
The system shall allow user to add the applicable test cases (i.e., Test Methods) to their test suite.

##### CSA-2967 (Functional Requirement)
The system shall allow user to classify Test Methods by Type.
Note: Certain test case types may not be available in the template(s) for preliminary test method evaluation if Test Methods are classified by type since a template can be configured to filter for types of Test Methods.

##### CSA-2968 (Functional Requirement)
The system shall allow the users to decide the scope of traceability query. Project, document, item type, etc.

##### CSA-2969 (Functional Requirement)
The system shall display requirements with no linked test cases, no linked executed test cases, and the status of execution of the test cases in the traceability page screen.

##### CSA-2970: The system shall display latest execution result, or results from a specific run (Functional Requirement)

##### CSA-2971: The system shall provide user the ability to select the following: * Authoring o... (Functional Requirement)
The system shall provide user the ability to select the following:
1. Authoring of Design Validation and Verification Plans, Protocols, and Reports.
2. Execution of test methods and recording of results.
3. Identification, definition, and selection of Test Methods as they correspond to Risk Records (Quads) and Design Requirements which they validate or verify.
4. Reuse of DV&V Protocols and Test Methods (Test Cases) across multiple test run executions.
5. Reuse with ability to make product specific modifications of DV&V Protocols and Test Methods prior to validation and subject to approval.
6. Allow for preliminary test method

##### CSA-2972 (Functional Requirement)
The system shall allow users to add attachment(s) as attachments on the actual results field

##### CSA-2973 (Functional Requirement)
The system shall allow users to add attachment(s) as attachments on the actual results field

##### CSA-2974 (Functional Requirement)
The system shall provide users to give results to test case (e.g. Pass/Fail) based on the rationale

##### CSA-2975 (Functional Requirement)
The system shall provide users the ability to write the rationale or pasted into the rich text area of the actual results field

##### CSA-2976 (Functional Requirement)
The system shall provide users the ability to reuse DV&V Protocols and Test Cases across multiple test run executions.
i.e. Reuse with ability to make product specific modifications of DV&V Protocols and Test Cases prior to validation and subject to approval.

##### CSA-2977: The system shall provide user the ability to select the following: * Authoring o... (Functional Requirement)
The system shall provide user the ability to select the following:
1. Authoring of Design Validation and Verification Plans, Protocols, and Reports.
2. Execution of test methods and recording of results.
3. Identification, definition, and selection of Test Methods as they correspond to Risk Records (Quads) and Design Requirements which they validate or verify.
4. Reuse of DV&V Protocols and Test Methods (Test Cases) across multiple test run executions.
1. Reuse with ability to make product specific modifications of DV&V Protocols and Test Methods prior to validation and subject to approval.
6. Allow for preliminary test method evaluation as well as Formal Verification and Validation use of the same test cases

##### CSA-2978 (Functional Requirement)
The system shall provide users the ability to track coverage of associated test case requirements down to execution of results

##### CSA-2979: The system shall provide user the ability to select the following: * Track cover... (Functional Requirement)
The system shall provide user the ability to select the following:
1. Track coverage of associated requirements down to execution results
2. Allow rationale for pass/fail/other verdict to be captured related to attached test result

##### CSA-2980: The system shall provide user with custom reports reported in Tabular format (Functional Requirement)

##### CSA-2981: The system shall display the following fields in the custom reports: (Functional Requirement)

##### CSA-2982: The system shall allow users to comment on the reports in Tabular format (Functional Requirement)

##### CSA-2983 (Functional Requirement)
The system shall provide ability to Mark a Comment as Resolved once the comment change is implemented or denied.

#### CSA-2984: Test Method Management (Heading)

##### CSA-2985: FS-TM-001.1 The system shall provide user the ability to BRANCH or REUSE documen... (Functional Requirement)
| FS-TM-001.1 | The system shall provide user the ability to BRANCH or REUSE document - If branched, the user identifies whether they wish to specify a certain revision to freeze at, or to float with the Head of the original - If reused, user chooses either clone/copy or derived options depending on the degree of design ownership the user is endowed with for this product. |
| --- | --- |
| FS-TM-001.2 | The system shall provide user the ability to branch or reuse document to the appropriate project and space |

##### CSA-2986: The system shall provide user the ability to remove items that are not needed (Functional Requirement)

##### CSA-2987 (Functional Requirement)
The system shall provide the ability to utilize a document with appropriate lifecycle and restrictions

##### CSA-2988 (Functional Requirement)
The system shall provide user, if branched the ability to overwrite specific to the new device or product and subsequently these changes in master or branch could be MERGED to the other.

##### CSA-2989 (Functional Requirement)
The system shall provide user the ability to manually import test method results from external test execution systems

##### CSA-2990 (Functional Requirement)
The system shall provide user the ability to define, trace (linkage of work items to each other), and report Test Methods as they address Design Requirements, Design Risk Controls, and Process Qualifications and Risk Mitigations.

##### CSA-2991: Reuse of Test Methods and their associated items within and across projects (Functional Requirement)

##### CSA-2992 (Functional Requirement)
The system shall provide user the ability to facilitate peer reviews and release into external document systems, e.g. Master Control

##### CSA-2993 (Functional Requirement)
The system shall allow reporting or querying of where Work Items are in use, and their state as related to the status of the Document workflow.

##### CSA-2994 (Functional Requirement)
The system shall provide user the ability to manage the change of existing and addition of new test methods in documents shared across multiple Polarion projects

##### CSA-2995 (Functional Requirement)
The system shall provide users ability to output a project or document state driven report:
Trace Work Items shared across multiple projects;
Perform Gap Analysis – based on System tracking of work items that are not completed in the linked configuration;
Perform Impact Analysis – based on System providing the links associated with a particular work item eg linked work items impacted by a change to a specific work item
The system may provide excel type reports showing work items and their linked work items

#### CSA-2996: Risk Management (Heading)

##### CSA-2997 (Functional Requirement)
The system shall provide Column headers from left to right.
(NOTE: some fields may be calculated based on values in other fields, e.g., "Residual Level")
Sample below; Refer to FM1305700 Rev 6 for current template
1. Index
2. Procedure Step
3. Perception
4. Cognition
5. Action
6. Use Error
7. "Use Error MDP Code"
8. Component Code
9. Hazard
10. Hazardous Situation
11. MDP Code
12. "Harm Code"
13. Severity
14. Initial Probability
15. Initial Risk Level
16. "Action Plan (where applicable)"
17. "Controls / Results (where applicable)"
18. Residual Probability
19. Residual Risk Level
20. Product
21. P1 #
22. P1 %
23. Rate
24. P2 %
25. P1xP2
26. P

##### CSA-2998 (Functional Requirement)
The system shall provide users ability to reference procedural steps from the Instructions for Use (IFU) document as input to the UFMEA analysis

##### CSA-2999 (Functional Requirement)
The system shall provide users ability to link warnings, precautions, and instruction outputs from UFMEA to the IFU, where applicable

##### CSA-3000 (Functional Requirement)
The system shall provide users ability to reuse Harms and corresponding severities across projects

##### CSA-3001 (Functional Requirement)
The system shall provide users ability to reuse Potential Causes, Hazards, and Hazardous Situations and their associated items within and across projects.

##### CSA-3002 (Functional Requirement)
The system shall allow document lifecycle management for collaboration within Polarion for Documents (states to be defined e.g. draft, review, release) containing Harms, Benefits, and Risks (Benefits and Risk Analysis) and in accordance with Risk Management Plan
Ref 2.2.1 (9) SD-462 Guidance to BD-PI Functional Specification

##### CSA-3003 (Functional Requirement)
The system shall provide users ability to facilitate peer reviews and release into external document systems (eg. MasterControl)

##### CSA-3004 (Functional Requirement)
The system shall provide users ability to report or query where Work Items are in use, and their state as relative to the Document Workflow states (e.g. draft, review, release) of the Documents where they appear.
Ref 2.2.1 (9) SD-462 Guidance to BD-PI Functional Specification

##### CSA-3005 (Functional Requirement)
The system shall provide users ability to manage the update of existing and addition of new risk items in documents shared across multiple Polarion projects

##### CSA-3006 (Functional Requirement)
The system shall provide users ability to output a project or document state driven report:
Trace Work Items shared across multiple projects;
Perform Gap Analysis – based on System tracking of work items that are not completed in the linked configuration;
Perform Impact Analysis – based on System providing the links associated with a particular work item eg linked work items impacted by a change to a specific work item
The system may provide excel type reports showing work items and their linked work items

##### CSA-3007 (Functional Requirement)
The system shall allow user ability to compare original risk document (eg FMEA) with red-lined changes

##### CSA-3008 (Functional Requirement)
The system shall allow user ability to incorporate Functional Block Diagrams in FMEAs

##### CSA-3009 (Functional Requirement)
The system shall allow automated or calculated entries to be over-written with manual entries for roles with appropriate access

##### CSA-3013 (Functional Requirement)
The system shall provide users ability to access and select IMDRF coding listings ie Annex A, Annex E, Annex F, Annex G

#### CSA-3014: Manufacturing Process Control Plan (Heading)

##### CSA-3015 (Functional Requirement)
The system shall allow users to author or reuse a Protocol (CQ, IQ, OQ, and PQ), Validation Plan and Report.
Provide traceability to site, materials, equipment, test methods and test results as applicable

##### CSA-3016 (Functional Requirement)
User shall be able to generate a report that presents the information contained in the Process Control Plan and associated pFMEA failure modes.

##### CSA-3017 (Functional Requirement)
User shall be able to select from qualification types: Process; CQ, TMV, Cleaning, Software, Spreadsheet, Cleanroom, Sterilisation, Other

##### CSA-3018 (Functional Requirement)
The system shall provide users ability to link to KPOV and related elements for process qualifications.

##### CSA-3019 (Functional Requirement)
The system shall provide users ability to link to Product, Site, Process Step, Equipment, Test Method, TMV Work Items as applicable

##### CSA-3020 (Functional Requirement)
The systems shall provide users ability to link to Deviations Work Item for Test Results and track resolution

##### CSA-3021: The system shall provide users ability to execute testing and record results (Functional Requirement)

##### CSA-3022 (Functional Requirement)
The system shall provide users ability to support Scrap Coding and linkage to defects and associated images

##### CSA-3023 (Functional Requirement)
The system shall provide users ability to generate pFMEA and process control plan reports

##### CSA-3024 (Functional Requirement)
The system shall provide users ability to facilitate peer reviews and release into external document systems (eg. MasterControl)

##### CSA-3025 (Functional Requirement)
The system shall allow reporting or querying of where Work Items are in use, and their state as related to the status of the Document workflow.

##### CSA-3026 (Functional Requirement)
The system shall provide users ability to manage the change of existing and addition of new requirements in documents shared across multiple Polarion projects

##### CSA-3027 (Functional Requirement)
The system shall provide users ability to output a project or document state driven report:
Trace Work Items shared across multiple projects;
Perform Gap Analysis – based on System tracking of work items that are not completed in the linked configuration;
Perform Impact Analysis – based on System providing the links associated with a particular work item eg linked work items impacted by a change to a specific work item
The system may provide excel type reports showing work items and their linked work items

#### CSA-3028: Test Method Validation Management (Heading)

##### CSA-3029: The system shall allow users to search for a particular Test Method (Functional Requirement)

##### CSA-3030 (Functional Requirement)
The system shall allow users to select Test Method and inspect the related TMV results

##### CSA-3031 (Functional Requirement)
The system shall allow users to view the linked worked items section to determine the Test Method Validation results used to validate this Test Method

##### CSA-3032 (Functional Requirement)
The system shall provide users ability to execute Test Method Validations and recording of results

##### CSA-3074 (Functional Requirement)
The system shall provide users ability to reuse TMV Protocols and Test Cases across multiple test run executions

##### CSA-3033 (Functional Requirement)
The system provides users ability to run preliminary testing prior to full validation

##### CSA-3034 (Functional Requirement)
The system allows rationale for pass/fail or other verdict to be captured related to attached test results

##### CSA-3075 (Functional Requirement)
The system provides users ability to reuse Test Method Validation protocols and their associated items within and across projects

##### CSA-3073 (Functional Requirement)
The system provides users ability to reuse Test Method Validation protocols and their associated items within and across projects

##### CSA-3035 (Functional Requirement)
The system provides users ability for lifecycle management (collaboration and status within Polarion) for Documents containing Test Method Validation protocols.

##### CSA-3036 (Functional Requirement)
The system shall provide users ability to facilitate peer reviews and release into external document systems (eg. MasterControl)

##### CSA-3037 (Functional Requirement)
The system shall allow reporting or querying of where Work Items are in use, and their state as related to the status of the Document workflow.

##### CSA-3038 (Functional Requirement)
The system shall provide users ability to manage the change of existing and addition of new requirements in documents shared across multiple Polarion projects

##### CSA-3039 (Functional Requirement)
The system shall provide users ability to output a project or document state driven report:
Trace Work Items shared across multiple projects;
Perform Gap Analysis – based on System tracking of work items that are not completed in the linked configuration;
Perform Impact Analysis – based on System providing the links associated with a particular work item eg linked work items impacted by a change to a specific work item
Note: The system may provide excel type reports showing work items and their linked work items

##### CSA-3040 (Functional Requirement)
The system shall allow users to manually over-write automated or calculated entries for roles with appropriate access and authorization

#### CSA-3041: Shared Libraries Management (Heading)

##### CSA-3042 (Functional Requirement)
The system shall allow user to identify content that needs to be changed. (e.g., Standard has changed)

##### CSA-3043 (Functional Requirement)
The system shall allow user to run an Impact Analysis report in Polarion to see where the shared item is linked

##### CSA-3044 (Functional Requirement)
The system shall allow user to decide impact and makes the changes.
(Or the user alerts parties responsible for items linked to shared library item(s) being changed that changes are happening)

##### CSA-3045 (Functional Requirement)
The system shall allow Owner of related items (via internal process) to link to the new content, or stay at the existing revision.

##### CSA-3046 (Functional Requirement)
The system shall define and provide users ability to reuse a Master Risk Management Library with links to FMEAs for each product family

##### CSA-3047 (Functional Requirement)
The system shall define and provide users ability to reuse a Master Test Method Documents Library
List of Test Method documents in server with links to TMV, Standards and Products

##### CSA-3048 (Functional Requirement)
The system shall define and provide users ability to reuse of a Master Test Method Validation Protocol Library

##### CSA-3049 (Functional Requirement)
The system shall define and provide users ability to reuse of a Master Procedure Sequence Library (Clinical Use Conditions/Steps by Product)

##### CSA-3050 (Functional Requirement)
The system shall define and provide users ability to reuse a Master Normative Requirements Library

##### CSA-3051 (Functional Requirement)
The system shall provide users ability to index all materials (components) and device part numbers in a Master Product Library, including Table of Product Families (Projects) and their product work items and their related SKU (device part no.’s) work items

##### CSA-3052 (Functional Requirement)
The system shall provide users ability to reference Statutory Sources and SOP's.
In exceptional cases, specific SOP's may be imported to provide specific requirements for traceability reporting:
Section under Documents and Pages for SOPs and Statutory Sources and a Report list of them

##### CSA-3053 (Functional Requirement)
The system shall provide users ability to reference Product and Procedural Sources such as VOC's, Company Standards, HCP Regulations, and HEOR:
Sub-space under Documents and Pages for Product and Procedural Sources (company standards and industry guidance); Report that lists the source documents

##### CSA-3054 (Functional Requirement)
The system shall allow users ability to report or query where items are in use, and if there are multiple versions, their version

##### CSA-3055 (Functional Requirement)
The system shall provide users ability to output a project or document state driven report:
Trace Work Items shared across multiple projects;
Perform Gap Analysis – based on System tracking of work items that are not completed in the linked configuration;
Perform Impact Analysis of Shared Library items – based on System providing the links associated with a particular work item eg linked work items impacted by a change to a specific work item
The system may provide excel type reports showing work items and their linked work items

#### CSA-3056: Reports (Heading)

##### CSA-3057 (Functional Requirement)
The system shall allow user to navigate to the page for generating appropriate risk report

##### CSA-3058: The system shall allow user to filter the report (Functional Requirement)

##### CSA-3059: The system shall allow user to configure the report (Functional Requirement)

##### CSA-3060 (Functional Requirement)
The system shall allow user to make changes to work item metadata fields using the Work item Properties Sidebar

##### CSA-3061: The system shall allow user to export the report in PDF or excel formats (Functional Requirement)

##### CSA-3062 (Functional Requirement)
The system shall allow users to navigate to the page for generating test case coverage reports

##### CSA-3063: The system shall allow users to filter to get to their desired subset of items (Functional Requirement)

##### CSA-3064 (Functional Requirement)
The system shall allow user to export the report in PDF using “Export to PDF function”

##### CSA-3065 (Functional Requirement)
The system shall allow users to navigate to the page for generating a Multi-level Trace table.

##### CSA-3066: The system shall allow users to filter to get to their desired subset of items (Functional Requirement)

##### CSA-3067: The system shall allow users to select inputs to view the Trace table (Functional Requirement)

##### CSA-3068 (Functional Requirement)
The system shall allow users to view the list of Work items that contain items traced down through the hierarchy.
Note: Traces may go to multiple endpoints in the same or different projects for each work item

##### CSA-3069 (Functional Requirement)
The system shall allow user to export the report in PDF using “Export to PDF function”
